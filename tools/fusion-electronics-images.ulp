#require 6.0200

string Version = "1.0";

#usage "en: <b>ThomsonLint Image Export</b>\n"
       "<p>"
       "Renders high-resolution PNGs of the schematic (per sheet) or "
       "board (top silk, bottom silk, and each used copper layer) for "
       "AI-assisted hardware design review with ThomsonLint."
       "<p>"
       "Run once from the schematic editor for sheet PNGs, then again "
       "from the board editor for layer PNGs."
       "<p>"
       "<b>Usage:</b>"
       "<blockquote>run fusion-electronics-images [-d] [-o prefix] [-r dpi]</blockquote>"
       "<b>Flags:</b>"
       "<blockquote>"
       "d: show a file dialog to choose the output prefix<br>"
       "o &lt;prefix&gt;: output prefix (default: &lt;repo&gt;/exports/&lt;design_name&gt;)<br>"
       "r &lt;dpi&gt;: override the per-mode DPI (50..2400)"
       "</blockquote>"
       "<b>Default DPI:</b>"
       "<blockquote>"
       "Schematic: 300 DPI (line+text content; higher gives no analysis benefit)<br>"
       "Board: 1200 DPI (resolves fine-pitch BGA / 0.2mm traces / 0402 silk for AI image analysis; use -r 600 if you prefer smaller files)"
       "</blockquote>"
       "Schematic outputs:"
       "<blockquote>"
       "&lt;prefix&gt;-img-sch-p&lt;N&gt;.png  (one per sheet)"
       "</blockquote>"
       "Board outputs:"
       "<blockquote>"
       "&lt;prefix&gt;-img-silk-top.png<br>"
       "&lt;prefix&gt;-img-silk-bot.png<br>"
       "&lt;prefix&gt;-img-cu-L&lt;num&gt;-&lt;name&gt;.png  (one per used copper layer)"
       "</blockquote>"
       "<p>"
       "<author>Author: ThomsonLint project</author>"

// ============================================================================
// Renders schematic and board into high-res PNGs by issuing EXPORT IMAGE
// commands through exit(). Run from the schematic editor for per-sheet
// PNGs; run from the board editor for top/bottom silk plus one PNG per
// used copper layer.
// ============================================================================

enum { false, true };

// Default DPI per mode. Schematics are line+text and don't benefit past 300;
// boards are physically small (~50mm) so 1200 is needed to resolve fine-pitch
// BGA / 0.2mm traces / 0402 silk for AI image analysis. Override either with
// -r <dpi> (e.g. -r 600 if you want smaller files for a coarse-pitch board).
int SCH_DPI = 300;
int BRD_DPI = 1200;
int DpiOverride = 0;   // 0 = use per-mode default

int isSchematic = 0;
int isBoard = 0;
int useFileDialog = false;
int useProvidedPrefix = false;
string Prefix;

if (schematic) isSchematic = 1;
if (board) isBoard = 1;

if (!isSchematic && !isBoard) {
  dlgMessageBox("ERROR: This ULP must be run from the schematic or board editor.");
  exit(1);
}

// parse command line arguments (supports any combination of -d, -o prefix, -r dpi)
int argi = 1;
while (argi < argc) {
  string flag = argv[argi];
  if (flag[0] != '-' || strlen(flag) != 2) {
    dlgMessageBox("Error: Invalid argument '" + flag + "'. Expected -d, -o <prefix>, or -r <dpi>.");
    exit(1);
  }
  switch (flag[1]) {
    case 'd':
      useFileDialog = true;
      argi++;
      break;
    case 'o':
      if (argi + 1 >= argc) {
        dlgMessageBox("Error: -o flag requires an output prefix.");
        exit(2);
      }
      Prefix = argv[argi + 1];
      useProvidedPrefix = true;
      argi += 2;
      break;
    case 'r':
      if (argi + 1 >= argc) {
        dlgMessageBox("Error: -r flag requires a DPI value (50..2400).");
        exit(2);
      }
      DpiOverride = strtol(argv[argi + 1]);
      if (DpiOverride < 50 || DpiOverride > 2400) {
        dlgMessageBox("Error: -r DPI must be 50..2400 (got " + argv[argi + 1] + ").");
        exit(2);
      }
      argi += 2;
      break;
    default:
      dlgMessageBox("Error: Unknown flag '" + flag + "'. Expected -d, -o <prefix>, or -r <dpi>.");
      exit(1);
  }
}

// --- Extract base design name from a path ---
string extractBaseName(string fullpath) {
  int lastSep = -1;
  int i;
  for (i = 0; i < strlen(fullpath); i++) {
    if (fullpath[i] == '/' || fullpath[i] == '\\') lastSep = i;
  }
  string base;
  if (lastSep >= 0) base = strsub(fullpath, lastSep + 1);
  else              base = fullpath;
  // strip extension
  int dotPos = -1;
  int j;
  for (j = strlen(base) - 1; j >= 0; j--) {
    if (base[j] == '.') { dotPos = j; break; }
  }
  if (dotPos > 0) base = strsub(base, 0, dotPos);
  // strip Fusion version suffix " v123"
  int len = strlen(base);
  int vPos = -1;
  for (j = len - 1; j >= 0; j--) {
    if (base[j] == 'v' && j > 0 && base[j - 1] == ' ') {
      int allDigits = 1;
      int k;
      for (k = j + 1; k < len; k++) {
        if (base[k] < '0' || base[k] > '9') { allDigits = 0; break; }
      }
      if (allDigits && (j + 1) < len) { vPos = j - 1; break; }
    }
  }
  if (vPos > 0) base = strsub(base, 0, vPos);
  // replace spaces with underscores
  string result = "";
  for (j = 0; j < strlen(base); j++) {
    if (base[j] == ' ') {
      result += "_";
    } else {
      string ch;
      sprintf(ch, "%c", base[j]);
      result += ch;
    }
  }
  return result;
}

string extractDir(string fullpath) {
  int lastSep = -1;
  int i;
  for (i = 0; i < strlen(fullpath); i++) {
    if (fullpath[i] == '/' || fullpath[i] == '\\') lastSep = i;
  }
  if (lastSep >= 0) return strsub(fullpath, 0, lastSep);
  return "";
}

// Sanitize a string for use in a filename
string sanitize(string s) {
  string out = "";
  for (int i = 0; i < strlen(s); i++) {
    char c = s[i];
    int ok = 0;
    if (c >= 'a' && c <= 'z') ok = 1;
    else if (c >= 'A' && c <= 'Z') ok = 1;
    else if (c >= '0' && c <= '9') ok = 1;
    else if (c == '-' || c == '_') ok = 1;
    string ch;
    if (ok) sprintf(ch, "%c", c);
    else    ch = "_";
    out += ch;
  }
  return out;
}

// Detect copper layer across EAGLE classic and Fusion Electronics conventions.
// Classic EAGLE: 1=Top, 16=Bottom, 2-15=inner (16 copper layers max).
// Fusion Electronics: 1=Top, 304=Bottom, 257..303=inner copper (default named
//   "Route17".."Route63" but commonly user-renamed e.g. "POWER", "GND_INNER").
//   Range observed in real 4-layer Fusion board (comet_brd, 2026-05-09).
// Falls back to name matching for layer-name renames that survive renumbering.
int IsCopperLayer(int layerNum, string layerName) {
  string upper = strupr(layerName);
  // Numeric ranges
  if (layerNum >= 1 && layerNum <= 16) return 1;          // EAGLE classic
  if (layerNum >= 257 && layerNum <= 304) return 1;        // Fusion extended copper
  if (layerNum == 63 || layerNum == 64) return 1;          // legacy / variant
  // Name-based fallback (catches user-renamed layers in unusual numeric slots)
  if (upper == "TOP" || upper == "BOTTOM") return 1;
  if (strstr(upper, "ROUTE") != -1) return 1;
  if (strstr(upper, "INNER") != -1) return 1;
  return 0;
}

// Determine output prefix
if (useFileDialog) {
  Prefix = dlgFileSave("ThomsonLint Image Export — output prefix", "", "");
  if (Prefix == "") exit(0);
} else if (!useProvidedPrefix) {
  string ulpDir = extractDir(argv[0]);
  string repoDir = extractDir(ulpDir);
  string exportDir = repoDir + "/exports";
  string designName = "";
  if (isSchematic) schematic(SCH) designName = extractBaseName(SCH.name);
  if (isBoard)     board(B)     designName = extractBaseName(B.name);
  Prefix = exportDir + "/" + designName;
}

// ============================================================================
// BUILD COMMAND SCRIPT
// ============================================================================

string script = "";
int imageCount = 0;

// Resolve the active DPI for this run: explicit -r override, or per-mode default.
int activeDpi = DpiOverride;
if (activeDpi == 0) {
  if (isSchematic) activeDpi = SCH_DPI;
  else             activeDpi = BRD_DPI;
}

if (isSchematic) {
  int sheetCount = 0;
  schematic(SCH) SCH.sheets(SH) sheetCount++;

  if (sheetCount == 0) {
    dlgMessageBox("No sheets found in schematic.");
    exit(1);
  }

  for (int s = 1; s <= sheetCount; s++) {
    string line;
    sprintf(line, "EDIT .s%d;\nWINDOW FIT;\nEXPORT IMAGE '%s-img-sch-p%d.png' %d;\n",
            s, Prefix, s, activeDpi);
    script += line;
    imageCount++;
  }
}

if (isBoard) {
  // Recalculate polygons so pours render as filled regions in EXPORT IMAGE.
  // Without this, polyPours show only as outlines and the review images miss
  // ground/power flood coverage entirely.
  script += "RATSNEST;\n";

  // Top silkscreen: 20 Dimension + 21 tPlace + 25 tNames + 51 tDocu
  string topSilk;
  sprintf(topSilk, "DISPLAY NONE 20 21 25 51;\nWINDOW FIT;\nEXPORT IMAGE '%s-img-silk-top.png' %d;\n",
          Prefix, activeDpi);
  script += topSilk;
  imageCount++;

  // Bottom silkscreen: 20 Dimension + 22 bPlace + 26 bNames + 52 bDocu
  string botSilk;
  sprintf(botSilk, "DISPLAY NONE 20 22 26 52;\nWINDOW FIT;\nEXPORT IMAGE '%s-img-silk-bot.png' %d;\n",
          Prefix, activeDpi);
  script += botSilk;
  imageCount++;

  // Pre-scan: a layer's L.used flag flips true only when a WIRE is drawn on it.
  // Fusion 4-layer boards often have inner copper that carries only a polygon
  // pour (e.g. an inner ground plane with no traces); those layers report
  // L.used == 0 and would be skipped. Mark a layer "in use" if it has a wire,
  // a via, OR a polygon pour on it.
  int hasPoly[];
  int hasWire[];
  int hasVia[];
  board(B) {
    B.signals(S) {
      S.polyPours(PO) { hasPoly[PO.layer] = 1; }
      S.wires(W)      { hasWire[W.layer]  = 1; }
      S.vias(V) {
        // a via spans a layer range; mark every copper layer in that range
        // (we don't know the exact range from V, so mark all known coppers)
        // Simpler: don't try — vias alone don't justify a per-layer image.
      }
    }
  }

  // Per-copper-layer view. Layer set chosen so the image shows:
  //   - traces and pour fills (from the copper layer itself, after RATSNEST)
  //   - via/THT-pad locations (17 Pads, 18 Vias) so trace-to-pad spacing is visible
  //   - unrouted airwires (19 Unrouted) so incomplete routing is flagged
  //   - component outlines for spatial context (21 tPlace, 22 bPlace)
  //   - keepout/restrict zones that constrain routing
  //     (39 tRestrict, 40 bRestrict, 41 vRestrict, 42 cRestrict)
  //   - board outline (20 Dimension)
  string detectedSummary = "";
  int copperImagesQueued = 0;
  board(B) {
    B.layers(L) {
      if (!IsCopperLayer(L.number, L.name)) continue;
      // Accept the layer if EAGLE marks it used OR if anything (wire/poly) is on it.
      int inUse = L.used || hasWire[L.number] || hasPoly[L.number];
      if (!inUse) continue;

      string layerCmd;
      sprintf(layerCmd,
              "DISPLAY NONE 20 17 18 19 21 22 39 40 41 42 %d;\nWINDOW FIT;\nEXPORT IMAGE '%s-img-cu-L%d-%s.png' %d;\n",
              L.number, Prefix, L.number, sanitize(L.name), activeDpi);
      script += layerCmd;
      imageCount++;
      copperImagesQueued++;

      string tag;
      sprintf(tag, "L%d(%s)%s%s%s ", L.number, L.name,
              L.used ? "" : "[!used]",
              hasWire[L.number] ? "" : "[no-wires]",
              hasPoly[L.number] ? "[poly]" : "");
      detectedSummary += tag;
    }
  }

  // Restore default layer visibility so the user's view isn't left in a partial state.
  script += "DISPLAY ALL;\n";

  // Stash the detection summary so it's surfaced in the final status line.
  if (copperImagesQueued > 0) {
    string note;
    sprintf(note, "Copper layers exported: %s", detectedSummary);
    status(note);
  }
}

if (imageCount == 0) {
  dlgMessageBox("Nothing to export — no sheets or used copper layers found.");
  exit(0);
}

string summary;
sprintf(summary, "ThomsonLint Image Export: queued %d image(s) at %d DPI.\nPrefix: %s",
        imageCount, activeDpi, Prefix);
status(summary);

// Dispatch the script. After this the ULP terminates and EAGLE/Fusion runs the
// commands in sequence. EXPORT IMAGE is synchronous, so each completes before
// the next begins.
exit(script);
